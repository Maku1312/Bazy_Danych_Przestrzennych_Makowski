FME workspace mapbox_upload.fmw
Startup Python:
      import rasterio

Creator
    GEOMTYPE = Geometry Object
    NUM = 1
    CREATED -> HTTPCaller
HTTPCaller
    CONNECTION_TIMEOUT_LENGTH = 60
    ERROR_ATTR = _error
    FOLLOW_REDIRECTS = FOLLOW_WITH_GET
    HTTP_METHOD = POST
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://api.mapbox.com/uploads/v1/maku1312/credentials?access_token=sk.eyJ1IjoibWFrdTEzMTIiLCJhIjoiY2xkMGxiaXJsMHRzcTNzbzFvanV6eGM4ZiJ9.z7_d5Bzam0D7zbFkUXGV6A
    TRANSFER_TIMEOUT_LENGTH = 90
    UPLOAD_CONTENT_TYPE = Text (text/plain)
    UPLOAD_FILE = $(FME_MF_DIR_ENCODED)T2019_POI_TABLE.zip
    UPLOAD_TYPE = Upload From File
    USE_COOKIES = No
    VERIFY_SSL_CERTIFICATES = Yes
    -> AttributeCreator
AttributeCreator
    ATTR_TABLE = SET_TO command = curl -X POST -H "Content-Type: application/json" -H "Cache-Control: no-cache" -d "{\"url\":\"http://tilestream-tilesets-production.s3.amazonaws.com/ae/_pending/flp6gfvrpp82uei01t4ul0dlc/maku1312\",\"tileset\":\"maku1312.T2019_POI_TABLE\",\"name\":\"T2019_POI_TABLE\"}" https://api.mapbox.com/uploads/v1/maku1312?access_token=sk.eyJ1IjoibWFrdTEzMTIiLCJhIjoiY2xkMGxiaXJsMHRzcTNzbzFvanV6eGM4ZiJ9.z7_d5Bzam0D7zbFkUXGV6A
    -> SystemCaller
SystemCaller
    CMD = @Value(command)
    -> Inspector
Inspector
